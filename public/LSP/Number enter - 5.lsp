9.Number enter - 5


(DEFUN C:5(/ A N NEW AN INDEX B1 B C D B1 B2)
(SETVAR "CMDECHO" 0)
(SETQ a (SSGET))
(SETQ N 1)
(SETQ AN (SSLENGTH A))
(SETQ INDEX 0)
(REPEAT An
(SETQ BP1(SSNAME A INDEX))
(SETQ B1 (ENTGET BP1))
(SETQ INDEX (1+ INDEX))
(SETQ B (ASSOC 0 B1))
(IF (= "TEXT" (CDR B))
(PROGN
(SETQ C (ASSOC 1 B1))
(REDRAW BP1 3)
(SETQ NEW (GETSTRING 1 (STRCAT "\nNEW TEXT<" (CDR C) "> : ")))
(REDRAW BP1 4)
(IF (/= NEW "")(PROGN
(SETQ D11 (CONS (CAR C) NEW)))(SETQ D11 (CONS (CAR C) (CDR C))))
(SETQ B2 (SUBST D11 C B1))
(ENTMOD B2))))(prin1)
(SETVAR "CMDECHO" 1))
